# GearSystems

## #1: GearSystems Requirements (Container)
These requirements define the system level behavior of the landing gear

### #3: UAS X shall have three landing gear subsystems named "LeftMainGear", "RightMainGear", and "NoseGear" (Functional)

### #4: The gear shall be considered "Retracted" or "up" when the upper limit switch has been closed (Functional)

### #5: The landing gear shall be considered "Extended" or "down" when the lower limit switch is closed and locked (Functional)

### #6: The lower limit switch shall be considered locked when it has been closed for 3 continuous seconds (Functional)

## #7: Weight On Wheels (WoW) (Container)

### #8: The WoW limit swich shall be enabled when all gear is down and locked AND AltitudeAGL is below 50 ft (Functional)

### #10: WoW shall be latched when the WoW limit switched has been closed for 3 seconds (Functional)
