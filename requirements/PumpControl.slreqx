# PumpControl

## #1: Pump control (Container)

### #2: The pump control shall recieve enumerated states of "up" or "down" (Functional)

### #4: The pump control shall return enumerated states of "on" or "off" (Functional)

### #6: The pump control shall return "on" when the pump is controlled in the commanded direction (Functional)
