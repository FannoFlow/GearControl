# GearControl

## #1: Gear Control (Container)
Encompasing requirements which validate the landing gear control functionality

### #2: The landing gear controller shall recieve the desired gear state of "up" or "down" (Functional)

### #3: The landing gear controller shall return the commanded gear state of "up" or "down" (Functional)

### #6: Gear command "up" disabled conditions (Functional)
The gear command "up" shall be disabled when any of the following are true:
* WoW is latched
* Altitude AGL is below 50 feet

### #7: The gear controller shall command gear "down" on startup (Functional)

### #8: Gear selection shall be disabled for 5 seconds after startup (Functional)
- Rationale: AltitudeAGL requires a stable sensor state for an accurate measurement. Five seconds is to allow for presure, GPS, and laser measurements to stabalize and return averaged readings before allowing the AlltitudeAGL gear lockout path.

### #10: Gear command "down" disabled conditions (Functional)
The gear command "down" shall be disabled when any of the following are true:
* Indicated airspeed is above 200 kts
